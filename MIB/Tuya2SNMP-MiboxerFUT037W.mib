Tuya2SNMP-MiboxerFUT037W DEFINITIONS ::= BEGIN

IMPORTS
	OBJECT-TYPE, NOTIFICATION-TYPE, Integer32
		FROM SNMPv2-SMI
	DisplayString, TruthValue
		FROM SNMPv2-TC
	tuyadevices, DeviceIndex
		FROM Tuya2SNMP;

miboxerFUT037W    			OBJECT IDENTIFIER ::= { tuyadevices 101 }
miboxerFUT037WdpUpdate      OBJECT IDENTIFIER ::= { miboxerFUT037W 2 }

-------------------------
-- Textual conventions --
-------------------------
 
WorkMode ::= TEXTUAL-CONVENTION
	DISPLAY-HINT   "d"
	STATUS         current
	DESCRIPTION    ""
	SYNTAX         INTEGER {
		white(0),
		colour(1),
		scene(2),
		music(3)
	}
	
-------------------------
-- Switches -------------
-------------------------

miboxerFUT037WdevicesTable OBJECT-TYPE
	SYNTAX SEQUENCE OF DeviceEntry
	ACCESS not-accessible
	STATUS mandatory
	DESCRIPTION ""
	::= { miboxerFUT037W 1 }
	
miboxerFUT037WdeviceEntry OBJECT-TYPE
	SYNTAX DeviceEntry
	ACCESS not-accessible
	STATUS mandatory
	DESCRIPTION ""
	INDEX { miboxerFUT037WdeviceIndex }
	::= { miboxerFUT037WdevicesTable 1 }
	
DeviceEntry ::= SEQUENCE {
	miboxerFUT037WdpSwitch
		TruthValue,
	miboxerFUT037WdpWorkmode
		WorkMode,
	miboxerFUT037WdpBright
		INTEGER,
	miboxerFUT037WdpTemp
		INTEGER,
	miboxerFUT037WdpColour
		OCTET STRING,
	miboxerFUT037WcalcColourHue
		INTEGER,
	miboxerFUT037WcalcColourSaturation
		INTEGER,
	miboxerFUT037WcalcColourBrightness
		INTEGER
}

miboxerFUT037WdeviceIndex OBJECT-TYPE
	SYNTAX DeviceIndex
	ACCESS not-accessible
	STATUS mandatory
	DESCRIPTION ""
	::= { miboxerFUT037WdeviceEntry 1 }
   
miboxerFUT037WdpSwitch OBJECT-TYPE
	SYNTAX TruthValue
	ACCESS read-write
	STATUS mandatory
	DESCRIPTION ""
	::= { miboxerFUT037WdeviceEntry 20 }
	
miboxerFUT037WdpWorkmode OBJECT-TYPE
	SYNTAX WorkMode
	ACCESS read-write
	STATUS mandatory
	DESCRIPTION ""
	::= { miboxerFUT037WdeviceEntry 21 }
	
miboxerFUT037WdpBright OBJECT-TYPE
	SYNTAX INTEGER (10..1000)
	ACCESS read-write
	STATUS mandatory
	DESCRIPTION ""
	::= { miboxerFUT037WdeviceEntry 22 }
	
miboxerFUT037WdpTemp OBJECT-TYPE
	SYNTAX INTEGER (0..1000)
	ACCESS read-write
	STATUS mandatory
	DESCRIPTION ""
	::= { miboxerFUT037WdeviceEntry 23 }
	
miboxerFUT037WdpColour OBJECT-TYPE
	SYNTAX OCTET STRING
	ACCESS read-write
	STATUS mandatory
	DESCRIPTION ""
	::= { miboxerFUT037WdeviceEntry 24 }
	
miboxerFUT037WcalcColourHue OBJECT-TYPE
	SYNTAX INTEGER (0..1000)
	ACCESS read-write
	STATUS mandatory
	DESCRIPTION ""
	::= { miboxerFUT037WdeviceEntry 10001 }
	
miboxerFUT037WcalcColourSaturation OBJECT-TYPE
	SYNTAX INTEGER (0..1000)
	ACCESS read-write
	STATUS mandatory
	DESCRIPTION ""
	::= { miboxerFUT037WdeviceEntry 10002 }
	
miboxerFUT037WcalcColourBrightness OBJECT-TYPE
	SYNTAX INTEGER (10..1000)
	ACCESS read-write
	STATUS mandatory
	DESCRIPTION ""
	::= { miboxerFUT037WdeviceEntry 10003 }

-------------------------
-- Traps ----------------
-------------------------

miboxerFUT037WupdateDpSwitch NOTIFICATION-TYPE
	OBJECTS { miboxerFUT037WdpSwitch }
    STATUS current
    DESCRIPTION ""
	::= { miboxerFUT037WdpUpdate 20 }

miboxerFUT037WupdateDpWorkmode NOTIFICATION-TYPE
	OBJECTS { miboxerFUT037WdpWorkmode }
    STATUS current
    DESCRIPTION ""
	::= { miboxerFUT037WdpUpdate 21 }

miboxerFUT037WupdateDpBright NOTIFICATION-TYPE
	OBJECTS { miboxerFUT037WdpBright }
    STATUS current
    DESCRIPTION ""
	::= { miboxerFUT037WdpUpdate 20 }

miboxerFUT037WupdateDpTemp NOTIFICATION-TYPE
	OBJECTS { miboxerFUT037WdpTemp }
    STATUS current
    DESCRIPTION ""
	::= { miboxerFUT037WdpUpdate 23 }

miboxerFUT037WupdateDpColour NOTIFICATION-TYPE
	OBJECTS { miboxerFUT037WdpColour, miboxerFUT037WcalcColourHue, miboxerFUT037WcalcColourSaturation, miboxerFUT037WcalcColourBrightness }
    STATUS current
    DESCRIPTION ""
	::= { miboxerFUT037WdpUpdate 24 }

END
